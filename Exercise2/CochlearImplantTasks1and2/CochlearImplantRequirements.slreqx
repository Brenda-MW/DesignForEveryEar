# CochlearImplantRequirements

## SP: Signal Processing (Container)

### SP-02: Eight frequency channels (Functional)
The speech processor shall decompose the input signal into exactly 8 frequency subband channels.

#### INFO-01: Background: eight channels (Informational)
Research shows about eight frequency channels suffice for good speech intelligibility in a cochlear implant; beyond that, quality gains rarely justify the added complexity.

### SP-01: DC-blocking input filter (Functional)
The input signal shall be high-pass filtered to remove DC and sub-audio content before frequency analysis (3rd-order Butterworth, normalized cutoff 0.015).

### SP-03: Envelope extraction (non-negative) (Functional)
Each subband channel shall be full-wave rectified so that the signal driving each electrode is non-negative (an amplitude envelope).

### SP-04: Optional soft-threshold denoising (Functional)
The processor shall provide a selectable denoising stage that applies per-band soft thresholding to the subband signals.

## ST: Electrical Stimulation (Container)

### ST-01: Charge-balanced biphasic pulses (Functional)
Each stimulation pulse shall be biphasic and charge-balanced, i.e. the net charge (sum of the pulse samples) over one pulse period shall be zero.

### ST-02: Interleaved electrode stimulation (Functional)
No two electrode channels shall deliver a stimulation pulse at the same sample instant (continuous interleaved sampling).

### ST-03: Amplitude encodes loudness (Functional)
The amplitude of each electrode pulse shall be proportional to the envelope (loudness) of its corresponding frequency subband.
